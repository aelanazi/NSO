module aspan-day1 {
  namespace "http://com/example/aspanday1";
  prefix aspan-day1;

  import ietf-inet-types {
    prefix inet;
  }
  import tailf-ncs {
    prefix ncs;
  }

  augment /ncs:services {
  list aspan-day1 {
    key hostname;

    uses ncs:service-data;
    ncs:servicepoint aspan-day1;

    leaf hostname {
        type leafref {
          path "/ncs:devices/ncs:device/ncs:name";
        }
      }

    leaf cabinet {
      type string;
      mandatory true;
    }

    leaf location {
      type string;
      mandatory true;
    }

    leaf country {
      type enumeration{
        enum NL;
        enum DE;
        enum SK;
        enum PL;
        enum IE;
        enum CH;
        enum RO;
        enum HU;
        enum CZ;
        enum CORP;
       }
    }




  }
 }
}
