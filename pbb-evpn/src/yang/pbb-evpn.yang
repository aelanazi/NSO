module pbb-evpn {

    namespace "http://example.com/pbb-evpn";
    prefix pbb-evpn;

    import tailf-common { prefix tailf; }
    import tailf-ncs { prefix ncs; }

    import tailf-ned-cisco-ios-xr { prefix cisco-ios-xr; }

    description
        "PBB-EVPN RFS Service";

    revision 2018-10-11 {
        description
                "fully working version draft 0.9.";
    }

    revision 2018-09-23 {
        description
                "working draft 0.2.";
    }

    revision 2018-09-22 {
        description
                "Initial vision 0.1";
    }

    augment /ncs:services {
        list pbb-evpn {
            description "This is an RFS skeleton service";
            key vpn-id;

            leaf vpn-id {
                tailf:info "VPN Service Instance id";
                mandatory true;
                type uint32;
            }

            uses ncs:service-data;
            ncs:servicepoint pbb-evpn-servicepoint;

            leaf service-type {
                description "instance type Point-to-Point, multipoint-to-multipoint, Rooted-multipoint" ;
                mandatory true;
                type enumeration {
                    enum eline;
                    enum elan;
                    enum etree;
                }
            }

            leaf evi {
                description "EVPN Instance ID, Country DE allowed range 49,000 - 49,999, For
                                IA Connected=49102, Static:49103";
                mandatory true;
                type uint16 {
                    range "49000..49999";
                }
                // Use the following command to build the XPATH: do show run services pbb-evpn 1990 | display prefixes | display xpath 
                // XPATH is: /ncs:services/pbb-evpn:pbb-evpn[pbb-evpn:vpn-id='1990']/pbb-evpn:evi 49000
                // EVI must be unique and not used by any other service.
                must "not(/ncs:services/pbb-evpn:pbb-evpn[pbb-evpn:vpn-id !=current()/../vpn-id]/pbb-evpn:evi=current()/../evi)" {
                    error-message "EVI is already used by another service, please make sure to pick
                                        free EVI ID.";
                }
            }

            leaf customer-name {
                tailf:info "Customer Name";
                mandatory true;
                type string;
            }

            container eline {
                tailf:cli-add-mode;
                when "(../service-type = 'eline')";

                container route-target {
                    tailf:info "Specify Target VPN Extended Communities";
                    uses route-target-grouping {
                        refine rt-export {
                            max-elements 1;
                        }
                        refine rt-import {
                            max-elements 1;
                        }
                    }
                }

                list link {
                    tailf:info "PE-CE Attachment Point";
                    key link-id;
                    max-elements 2;

                    leaf link-id {
                        tailf:info "Link ID";
                        mandatory true;
                        type string;
                    }

                    uses main-grouping {
                    }
                }
            }

            container elan {
                tailf:cli-add-mode;
                when "(../service-type = 'elan')";

                container route-target {
                    tailf:info "Specify Target VPN Extended Communities";
                    uses route-target-grouping;
                }

                list link {
                    tailf:info "PE-CE Attachment Point";
                    key link-id;
                    min-elements 2;

                    leaf link-id {
                        tailf:info "Link ID";
                        mandatory true;
                        type string;
                    }

                    uses main-grouping {
                    }
                }
            }

            container etree {
                tailf:cli-add-mode;
                when "(../service-type = 'etree')";
                list link {
                    tailf:info "PE-CE Attachment Point";
                    key link-id;
                    min-elements 2;

                    leaf link-id {
                        tailf:info "Link ID";
                        mandatory true;
                        type string;
                    }

                    uses main-grouping {
                    }

                    leaf ce-type {
                        tailf:info "define CE type root or leaf eq hub or spoke";
                        type enumeration {
                            enum hub;
                            enum spoke;
                        }
                        default spoke;
                    }

                    leaf hub-route-target {
                        tailf:info "ASN:nn or IP-address:nn; Target VPN Extended Community exported
                                                by roots to all leaves";
                        when "(../ce-type = 'hub')";
                        type asn-ip-type {
                            tailf:info "ASN:nn or IP-address:nn;;Target VPN Extended Community";
                        }
                    }

                    leaf spoke-route-target {
                        tailf:info "ASN:nn or IP-address:nn; Target VPN Extended Community exported
                                                by roots to all leaves";
                        when "(../ce-type = 'spoke')";
                        type asn-ip-type {
                            tailf:info "ASN:nn or IP-address:nn;;Target VPN Extended Community";
                        }
                    }
                }
            }
            grouping main-grouping {
                leaf edge-i-sid {
                    tailf:info "Instance Service ID";
                    description "Instance Service ID, Country DE 4900000 to 4999999";
                    type uint32 {
                        range "4900000..4999999" {
                        }
                    }
                    // XPATH example: 
                    // /ncs:services/pbb-evpn:pbb-evpn[pbb-evpn:vpn-id='1990']/pbb-evpn:eline/pbb-evpn:link[pbb-evpn:link-id='site-a']/pbb-evpn:edge-i-sid 4900000
                    // /ncs:services/pbb-evpn:pbb-evpn[pbb-evpn:vpn-id='1990']/pbb-evpn:eline/pbb-evpn:link[pbb-evpn:link-id='site-b']/pbb-evpn:edge-i-sid 4900000
                    // Prevent the reuse of the SID ID for any service (E-LINE, E-LAN, E-Tree) The follwoin must statment makes sure the SID is unique.
                    // Ignore a node   *[not(*)] not working || tryied /*/ not working tried /./
                    //		"not(/ncs:services//*//*/pbb-evpn:link[pbb-evpn:link-id!=current()/../link-id]/pbb-evpn:edge-i-sid=current()/../edge-i-sid)" {	
                    // "not(/ncs:services/pbb-evpn:pbb-evpn[pbb-evpn:vpn-id !=current()/../vpn-id]/pbb-evpn:evi=current()/../evi)" 
                    must "count(/ncs:services/pbb-evpn:pbb-evpn[pbb-evpn:vpn-id =current()/../../../vpn-id]//pbb-evpn:link[pbb-evpn:link-id!=current()/../link-id]/pbb-evpn:edge-i-sid=current())
                                        = 0 and " +
                                        "count(/ncs:services/pbb-evpn:pbb-evpn[pbb-evpn:vpn-id !=current()/../../../vpn-id]//pbb-evpn:link[pbb-evpn:link-id!=current()/../link-id]/pbb-evpn:edge-i-sid=current())
                                        = 0 and " +
                                        "count(/ncs:services/pbb-evpn:pbb-evpn[pbb-evpn:vpn-id !=current()/../../../vpn-id]//pbb-evpn:link[pbb-evpn:link-id=current()/../link-id]/pbb-evpn:edge-i-sid=current())
                                        = 0 " {

                        //"count(/ncs:services/pbb-evpn:pbb-evpn[pbb-evpn:vpn-id !=current()/../../../vpn-id]/pbb-evpn:eline/pbb-evpn:link[pbb-evpn:link-id!=current()/../link-id]/pbb-evpn:edge-i-sid
                        //=current()) = 0 or " +
                        //"count(/ncs:services/pbb-evpn:pbb-evpn[pbb-evpn:vpn-id =current()/../../../vpn-id]/pbb-evpn:elan/pbb-evpn:link[pbb-evpn:link-id!=current()/../link-id]/pbb-evpn:edge-i-sid
                        //=current()) = 0 or " +
                        //"count(/ncs:services/pbb-evpn:pbb-evpn[pbb-evpn:vpn-id !=current()/../../../vpn-id]/pbb-evpn:elan/pbb-evpn:link[pbb-evpn:link-id!=current()/../link-id]/pbb-evpn:edge-i-sid
                        //=current()) = 0 or " +
                        //"count(/ncs:services/pbb-evpn:pbb-evpn[pbb-evpn:vpn-id =current()/../../../vpn-id]/pbb-evpn:etree/pbb-evpn:link[pbb-evpn:link-id!=current()/../link-id]/pbb-evpn:edge-i-sid
                        //=current()) = 0 or " +
                        //"count(/ncs:services/pbb-evpn:pbb-evpn[pbb-evpn:vpn-id !=current()/../../../vpn-id]/pbb-evpn:etree/pbb-evpn:link[pbb-evpn:link-id!=current()/../link-id]/pbb-evpn:edge-i-sid
                        //=current()) = 0 " {
                        error-message "I-SID (Instance Service ID) is already used by another service,
                                                please make sure to pick free I-SID ID.";
                    }
                }

                leaf pe-device {
                    tailf:info "Edge-PE where service will be configured";
                    type leafref {
                        path "/ncs:devices/ncs:device/ncs:name";
                    }
                }

                leaf svlan-id {
                    tailf:info "Service VLAN ID(S-Tag)";
                    mandatory true;
                    type uint16 {
                        range "1..4094" {
                            error-message "Service VLAN ID is out of range";
                        }
                    }
                }

                leaf interface-type {
                    type enumeration {
                        enum GigabitEthernet;
                        enum TenGigabitEthernet;
                    }
                    default GigabitEthernet;
                }

                container pe-port {
                    tailf:cli-add-mode;
                    leaf pe-gig-port {
                        tailf:info "Customer Facing Interface";
                        when "(../../interface-type = 'GigabitEthernet')";
                        type leafref {
                            path "deref(../../pe-device)/../ncs:config/cisco-ios-xr:interface/cisco-ios-xr:GigabitEthernet/cisco-ios-xr:id";
                        }
                        // /ncs:services/pbb-evpn:pbb-evpn[pbb-evpn:vpn-id !=current()/../../../vpn-id]/pbb-evpn:eline/pbb-evpn:link[pbb-evpn:link-id!=current()/../link-id]/

                        // nsoadmin@ncs# show running-config services pbb-evpn 101 | display prefixes | display xpath 
                        // /ncs:services/pbb-evpn:pbb-evpn[pbb-evpn:vpn-id='101']/pbb-evpn:service-type eline
                        // /ncs:services/pbb-evpn:pbb-evpn[pbb-evpn:vpn-id='101']/pbb-evpn:evi 49002
                        // /ncs:services/pbb-evpn:pbb-evpn[pbb-evpn:vpn-id='101']/pbb-evpn:customer-name Test1
                        // /ncs:services/pbb-evpn:pbb-evpn[pbb-evpn:vpn-id='101']/pbb-evpn:eline/pbb-evpn:route-target/pbb-evpn:rt-export[pbb-evpn:asn-ip='2:1']
                        // /ncs:services/pbb-evpn:pbb-evpn[pbb-evpn:vpn-id='101']/pbb-evpn:eline/pbb-evpn:route-target/pbb-evpn:rt-import[pbb-evpn:asn-ip='1:1']
                        // /ncs:services/pbb-evpn:pbb-evpn[pbb-evpn:vpn-id='101']/pbb-evpn:eline/pbb-evpn:link[pbb-evpn:link-id='1']/pbb-evpn:edge-i-sid 4900001
                        // /ncs:services/pbb-evpn:pbb-evpn[pbb-evpn:vpn-id='101']/pbb-evpn:eline/pbb-evpn:link[pbb-evpn:link-id='1']/pbb-evpn:pe-device deviosxr-lab-1
                        // /ncs:services/pbb-evpn:pbb-evpn[pbb-evpn:vpn-id='101']/pbb-evpn:eline/pbb-evpn:link[pbb-evpn:link-id='1']/pbb-evpn:svlan-id 300
                        // /ncs:services/pbb-evpn:pbb-evpn[pbb-evpn:vpn-id='101']/pbb-evpn:eline/pbb-evpn:link[pbb-evpn:link-id='1']/pbb-evpn:interface-type TenGigabitEthernet
                        // /ncs:services/pbb-evpn:pbb-evpn[pbb-evpn:vpn-id='101']/pbb-evpn:eline/pbb-evpn:link[pbb-evpn:link-id='1']/pbb-evpn:pe-port/pbb-evpn:pe-tengig-port 0
                        // /ncs:services/pbb-evpn:pbb-evpn[pbb-evpn:vpn-id='101']/pbb-evpn:eline/pbb-evpn:link[pbb-evpn:link-id='1']/pbb-evpn:nni-redundancy Protected
                        // /ncs:services/pbb-evpn:pbb-evpn[pbb-evpn:vpn-id='101']/pbb-evpn:eline/pbb-evpn:link[pbb-evpn:link-id='1']/pbb-evpn:Bundle-Ether/pbb-evpn:pe-port-tengig[pbb-evpn:pe-port='1']
                        // /ncs:services/pbb-evpn:pbb-evpn[pbb-evpn:vpn-id='101']/pbb-evpn:eline/pbb-evpn:link[pbb-evpn:link-id='1']/pbb-evpn:Bundle-Ether/pbb-evpn:pe-port-tengig[pbb-evpn:pe-port='2']
                        // /ncs:services/pbb-evpn:pbb-evpn[pbb-evpn:vpn-id='101']/pbb-evpn:eline/pbb-evpn:link[pbb-evpn:link-id='2']/pbb-evpn:edge-i-sid 4900002
                        // /ncs:services/pbb-evpn:pbb-evpn[pbb-evpn:vpn-id='101']/pbb-evpn:eline/pbb-evpn:link[pbb-evpn:link-id='2']/pbb-evpn:pe-device deviosxr-lab-2
                        // /ncs:services/pbb-evpn:pbb-evpn[pbb-evpn:vpn-id='101']/pbb-evpn:eline/pbb-evpn:link[pbb-evpn:link-id='2']/pbb-evpn:svlan-id 300
                        // /ncs:services/pbb-evpn:pbb-evpn[pbb-evpn:vpn-id='101']/pbb-evpn:eline/pbb-evpn:link[pbb-evpn:link-id='2']/pbb-evpn:pe-port/pbb-evpn:pe-gig-port 0
                        // /ncs:services/pbb-evpn:pbb-evpn[pbb-evpn:vpn-id='101']/pbb-evpn:eline/pbb-evpn:link[pbb-evpn:link-id='2']/pbb-evpn:nni-redundancy Protected
                        // /ncs:services/pbb-evpn:pbb-evpn[pbb-evpn:vpn-id='101']/pbb-evpn:eline/pbb-evpn:link[pbb-evpn:link-id='2']/pbb-evpn:Bundle-Ether/pbb-evpn:pe-port[pbb-evpn:pe-port='1']
                        // /ncs:services/pbb-evpn:pbb-evpn[pbb-evpn:vpn-id='101']/pbb-evpn:eline/pbb-evpn:link[pbb-evpn:link-id='2']/pbb-evpn:Bundle-Ether/pbb-evpn:pe-port[pbb-evpn:pe-port='2']

                        //must "not(/ncs:services/pbb-evpn:pbb-evpn[pbb-evpn:vpn-id !=current()/../../../../vpn-id]/pbb-evpn:eline/pbb-evpn:link[pbb-evpn:link-id
                        //                        !=current()/../../link-id][pbb-evpn:pe-device =current()/../../pe-device]/pbb-evpn:pe-port[pbb-evpn:pe-gig-port
                        //                        =current()]) and (/ncs:services/pbb-evpn:pbb-evpn[pbb-evpn:vpn-id !=current()/../../../../vpn-id]/pbb-evpn:eline/pbb-evpn:link[pbb-evpn:link-id
                        //                        !=current()/../../link-id][pbb-evpn:pe-device =current()/../../pe-device][pbb-evpn:svlan-id =current()/../../svlan-id])" {

                        //	../../../../../pbb-evpn[customer-name != current()/../../../../customer-name]/eline/link[pe-device=
                        //                        current()/../../pe-device][pe-port/pe-gig-port=current()]) = 0
                        //                        or count(../../../../../pbb-evpn[customer-name != current()/../../../../customer-name]/elan/link[pe-device=
                        //                        current()/../../pe-device][pe-port/pe-gig-port=current()]) = 0
                        //                        or count(../../../../../pbb-evpn[customer-name != current()/../../../../customer-name]/etree/link[pe-device=
                        //                        current()/../../pe-device][pe-port/pe-gig-port=current()]) = 0
                        //                        " {
                        //error-message "Interface is already used by another service, please make sure
                        //                             to pick free port.";
                        //}
                    }
                    leaf pe-tengig-port {
                        tailf:info "Customer Facing Interface";
                        when "(../../interface-type = 'TenGigabitEthernet')";
                        type leafref {
                            path "deref(../../pe-device)/../ncs:config/cisco-ios-xr:interface/cisco-ios-xr:TenGigE/cisco-ios-xr:id";
                        }
                        must "count(../../../../../pbb-evpn[customer-name != current()/../../../../customer-name]/eline/link[pe-device=
                                                current()/../../pe-device][pe-port/pe-tengig-port=current()])
                                                = 0 or count(../../../../../pbb-evpn[customer-name != current()/../../../../customer-name]/elan/link[pe-device=
                                                current()/../../pe-device][pe-port/pe-tengig-port=current()])
                                                = 0 or count(../../../../../pbb-evpn[customer-name != current()/../../../../customer-name]/etree/link[pe-device=
                                                current()/../../pe-device][pe-port/pe-tengig-port=current()])
                                                = 0 " {
                            error-message "Interface is already used by another service, please make sure
                                                        to pick free port.";
                        }
                    }
                }

                leaf nni-redundancy {
                    type enumeration {
                        enum None;
                        enum Protected;
                        enum Dual-PE;
                    }
                    default None;
                }

                container Bundle-Ether {
                    when "../nni-redundancy = 'Protected'";

                    list pe-port {
                        tailf:cli-suppress-mode;
                        tailf:cli-delete-when-empty;
                        when "(../../interface-type = 'GigabitEthernet')";
                        max-elements 7;
                        key pe-port;
                        leaf pe-port {
                            tailf:info "Customer Facing Interface";
                            type leafref {
                                path "deref(../../../pe-device)/../ncs:config/cisco-ios-xr:interface/cisco-ios-xr:GigabitEthernet/cisco-ios-xr:id";
                            }
                            mandatory true;
                        }
                        must "count(../../../../../pbb-evpn[customer-name != current()/../../../../customer-name]/eline/link[pe-device=
                                                current()/../../pe-device][Bundle-Ether/pe-port=current()]) =
                                                0 or count(../../../../../pbb-evpn[customer-name != current()/../../../../customer-name]/elan/link[pe-device=
                                                current()/../../pe-device][Bundle-Ether/pe-port=current()]) =
                                                0 or count(../../../../../pbb-evpn[customer-name != current()/../../../../customer-name]/etree/link[pe-device=
                                                current()/../../pe-device][Bundle-Ether/pe-port=current()]) =
                                                0" {
                            error-message "Interface is already used by another service, please make sure
                                                        to pick free port.";
                        }
                    }

                    list pe-port-tengig {
                        tailf:cli-suppress-mode;
                        tailf:cli-delete-when-empty;
                        when "(../../interface-type = 'TenGigabitEthernet')";
                        max-elements 7;
                        key pe-port;
                        leaf pe-port {
                            tailf:info "Customer Facing Interface";
                            type leafref {
                                path "deref(../../../pe-device)/../ncs:config/cisco-ios-xr:interface/cisco-ios-xr:TenGigE/cisco-ios-xr:id";
                            }
                            mandatory true;
                        }
                        must "count(../../../../../pbb-evpn[customer-name != current()/../../../../customer-name]/eline/link[pe-device=
                                                current()/../../pe-device][Bundle-Ether/pe-port-tengig=current()])
                                                = 0 or count(../../../../../pbb-evpn[customer-name != current()/../../../../customer-name]/elan/link[pe-device=
                                                current()/../../pe-device][Bundle-Ether/pe-port-tengig=current()])
                                                = 0 or count(../../../../../pbb-evpn[customer-name != current()/../../../../customer-name]/etree/link[pe-device=
                                                current()/../../pe-device][Bundle-Ether/pe-port-tengig=current()])
                                                = 0" {
                            error-message "Interface is already used by another service, please make sure
                                                        to pick free port.";
                        }
                    }
                }

                container Dual-PE {
                    when "../nni-redundancy = 'Dual-PE'";
                    leaf esi {
                        tailf:info "Ethernet Segment Identifier";
                        mandatory true;
                        type string {
                            pattern '[0300]+\.[4900]+\.[0-9a-fA-F]+' {
                                error-message "ESI is out of range please allocate within the following range:
                                                                0300.4900.0000 – 0300.4900.ffff";
                            }
                        }
                        description "Ethernet Segment Identifier, Country DE ESI Range: 0300.4900.0000
                                                – 0300.4900.ffff";
                    }
                }
            }

            grouping route-target-grouping {

                list "rt-export" {
                    tailf:info "Export Target-VPN community";
                    tailf:cli-suppress-mode;
                    tailf:cli-delete-when-empty;
                    key asn-ip;
                    leaf asn-ip {
                        type asn-ip-type {
                            tailf:info "ASN:nn or IP-address:nn;;Target VPN Extended Community";
                        }
                    }
                }

                list "rt-import" {
                    tailf:info "Import Target-VPN community";
                    tailf:cli-suppress-mode;
                    tailf:cli-delete-when-empty;
                    key asn-ip;
                    leaf asn-ip {
                        type asn-ip-type {
                            tailf:info "ASN:nn or IP-address:nn;;Target VPN Extended Community";
                        }
                    }
                }
            }

            // ASN IP type
            typedef asn-ip-type {
                type string {
                    tailf:info "ASN:nn or IP-address:nn";
                    pattern '(([0-9]+)|((([0-9]|[1-9][0-9]|1[0-9][0-9]|2[0-4][0-9]|25[0-5])'
                    +'\.){3}([0-9]|[1-9][0-9]|1[0-9][0-9]|2[0-4][0-9]|25[0-5]))):[0-9]+';
                }
            }
        }
    }
}
